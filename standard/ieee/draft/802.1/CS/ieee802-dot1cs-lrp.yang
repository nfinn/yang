module ieee802-dot1cs-lrp {
  yang-version 1.1;

  namespace "urn:ieee:std:802.1CS:yang:ieee802-dot1cs-lrp";
  prefix "dot1cs";

  import ietf-system { prefix "sys"; }
  import ieee802-dot1ab-types { prefix "lldp-types"; }
  import ietf-yang-types { prefix "yang"; }
  import ieee802-dot1q-types { prefix dot1qtypes; }
  import ietf-interfaces { prefix if; }
  import ieee802-types { prefix ieee; }
  import ietf-inet-types { prefix inet; }

  organization
    "Institute of Electrical and Electronics Engineers";
  contact
    "WG-URL: http://grouper.ieee.org/groups/802/1/
     WG-EMail: stds-802-1@ieee.org
       Contact: IEEE 802.1 Working Group Chair
       Postal: C/O IEEE 802.1 Working Group
       IEEE Standards Association
            445 Hoes Lane
            P.O. Box 1331
            Piscataway
            NJ 08855-1331
            USA

    E-mail: STDS-802-1-L@LISTSERV.IEEE.ORG";
 
  description
    "This YANG module is a prototype based on 802.1CS UML.";

  revision 2020-01-21 {
    description
      "IEEE P802.1CS Draft 2.6.
       January 21, 2020  ";
    reference
      "Update revision.
                        ";
  }
  /*--------------------*/
  /* Feature            */
  /*--------------------*/

  feature lrp {
    description
      "Feature Link-local Registration Protocol";
  }

  /*--------------------*/
  /* Type Definitions   */
  /*--------------------*/
  typedef lrp-dt-address-union {
    type union {
      type ieee:mac-address;
      type inet:ipv4-address;
      type inet:ipv6-address;
    }
  }

  /*--------------------*/
  /* Configuration Data */
  /*--------------------*/
  /*
    Link-local Registration Protocol
  */
  augment "/sys:system" {
    description "Link-local Registration Protocol";
    container lrp {
      if-feature lrp;
      description
        "Configure the Link-local Registration Protocol";
        leaf lrp-ack-timer-init {
          type uint32;
          units "milliseconds";
          config false;
          description
            "A read-only integer n specifying the number of milliseconds for
            ackTimerInit (D.2.12.6 of IEEE Std 802.1Q-2018)"; 
          reference
            "IEEE 802.1CS Clause 11.3.1";
        }
        leaf lrp-reconnect-max {
          type uint16;
          units "seconds";
          description
            "An integer number of seconds which is the maximum value for
            instReconnectReset.";
          reference
            "IEEE 802.1CS Clause 11.3.2";
        }
        list portal {
        key "portal-id";
        config false;
        leaf portal-id {
          type uint32;
          config false;
          description
            "Local Identifier of portal";
          reference
            "IEEE 802.1CS Clause 10";
        }
        leaf target-port-interface-ref {
          type if:interface-ref;
          config false;
          description
            "The interface reference identifying the target 
            port to which this portal is attached to.";
          reference
            "IEEE 802.1CS Clause (8.2.2.1)";
        }
        leaf lrp-dt-instance-id {
          type leafref {
            path "/sys:system/dot1cs:lrp/dot1cs:lrp-dt-instance/dot1cs:instance-id";
          }
          config false;
          description
            "The LRP-DT instance id that this portal is 
            attached to.";
          reference
            "IEEE 802.1CS Clause (8.2.2.1)";
        }
        leaf application-id {
          type string;
          config false;
          description
            "The value transmitted in, and expected to be received in, the
            appId field of Hello LRPDUs."; 
          reference
            "IEEE 802.1CS Clause (8.2.2.1)";
        }
        leaf my-chassis-id {
          type lldp-types:chassis-id-type ;
          config false;
          description
            "The value transmitted in the My Chassis ID TLV, and expected to be
            received in the Neighbor Chassis ID TLV, of Hello LRPDUs";
          reference
            "IEEE 802.1CS Clause (8.2.2.2)";
        }
        leaf my-port-id {
          type lldp-types:port-id-type ;
          config false;
          description
            "The value transmitted in the My Port ID TLV, and expected to be
            received in the Neighbor Port ID TLV, of Hello LRPDUs."; 
          reference
            "IEEE 802.1CS Clause (8.2.2.3)";
        }
        leaf neighbor-chassis-id {
          type lldp-types:chassis-id-type ;
          config false;
          description
            "The value transmitted in the Neighbor Chassis ID TLV, and expected
            to be received in the My Chassis ID TLV, of Hello LRPDUs.";
          reference
            "IEEE 802.1CS Clause (8.2.2.4)";
        }
        leaf neighbor-port-id {
          type lldp-types:port-id-type ;
          config false;
          description
            "The value transmitted in the Neighbor Port ID TLV, and expected to
            be received in the My Port ID TLV, of Hello LRPDUs."; 
          reference
            "IEEE 802.1CS Clause (8.2.2.5)";
        }
        leaf my-hello-status {
          type enumeration {
            enum hs-looking {
              value 1;
              description
                "This Portal has not yet received a successful Associate Portal
                request."; 
            }
            enum hs-connecting {
              value 2;
              description
                "This Portal has received a successful Associate Portal
                request, and a Hello LRPDU with the hsLooking status. The
                Portal is ready to receive all LRPDUs.";
            }
            enum hs-connected {
              value 3;
              description
                "This Portal is up and ready to transfer LRP application data.
                The Portal is allowed to transmit all LRPDUs.";
            }
          }
          config false;
          description
            "An enumerated value to be transmitted in the Hello status field
            of any Hello LRPDU.";
          reference
            "IEEE 802.1CS Clause (8.2.2.8)";
        }
        leaf local-overflow {
          type boolean;
          config false;
          description
            "Contains the last Boolean input from the Database overflow
            request. A value of TRUE indicates that the partner applicant
            database has exceeded the capacity of the local registrar LRP
            application."; 
          reference
            "IEEE 802.1CS Clause (8.2.2.10)";
        }
        leaf neighbor-overflow {
          type boolean;
          config false;
          description
            "A Boolean copied from the last-received database overflow bit [bit
            8] in the Error status field of the last-received Hello LRPDU.";
          reference
            "IEEE 802.1CS Clause (8.2.2.11)";
        }
        leaf neighbor-acknowledged {
          type boolean;
          config false;
          description
            "A Boolean, equal to the AND of all of the actAcknowledged
            variables for all of the Applicant state machines (records) on this
            Portal."; 
          reference
            "IEEE 802.1CS Clause (8.2.2.12)";
        }
        leaf my-app-hello-info {
          type string;
          config false;
          description
            "Value to put in the Application Information TLV of a
            transmitted Hello LRPDU."; 
          reference
            "IEEE 802.1CS Clause (8.2.2.16)";
        }
        leaf last-received-status {
          type string;
          config false;
          description
            "Used by the Receive Hello state machine to record the
            Hello status field of a Hello LRPDU received from the
            neighbor Portal."; 
          reference
            "IEEE 802.1CS Clause (8.2.2.22)";
        }
        leaf applicant-active-records {
          type uint32;
          config false;
          description
            "An integer reporting the number of records in the applicant
            database."; 
          reference
            "IEEE 802.1CS Clause (11.5.1)";
        }
        leaf registrar-active-records {
          type uint32;
          config false;
          description
            "An integer reporting the number of records in the registrar
            database."; 
          reference
            "IEEE 802.1CS Clause (11.5.2)";
        }
        leaf sent-hellos {
          type yang:counter64;
          config false;
          description
            "The number of Hello LRPDUs transmitted by the Send Hello state machines.";
          reference
            "IEEE 802.1CS Clause (11.5.3)";
        }
        leaf accepted-hellos {
          type yang:counter64;
          config false;
          description
            "The number of valid Hello LRPDUsreceived by the Receive Hello
            state machine."; 
          reference
            "IEEE 802.1CS Clause (11.5.4)";
        }
        leaf discarded-hellos {
          type yang:counter64;
          config false;
          description
            "The number of invalid Hello LRPDUs discarded by the Receive Hello
            state machine"; 
          reference
            "IEEE 802.1CS Clause (11.5.5)";
        }
        leaf sent-records  {
          type yang:counter64;
          config false;
          description
            "The number of Record LRPDUs transmitted by the Applicant state
            machine."; 
          reference
            "IEEE 802.1CS Clause (11.5.6)";
        }
        leaf accepted-records {
          type yang:counter64;
          config false;
          description
            "The number of valid Record LRPDUs received by the Partial list
            state machine."; 
          reference
            "IEEE 802.1CS Clause (11.5.7)";
        }
        leaf discarded-records {
          type yang:counter64;
          config false;
          description
            "The number of invalid Record LRPDUs discarded by the Partial list
            state machine."; 
          reference
            "IEEE 802.1CS Clause (11.5.8)";
        }
        leaf record-errors  {
          type yang:counter64;
          config false;
          description
            "The number of records discarded from otherwise-valid Record LRPDUs
            by regReceiveWriteRecord due to inconsistencies between the
            Checksum, Application data, and Data length fields."; 
          reference
            "IEEE 802.1CS Clause (11.5.9)";
        }
        leaf sent-partials  {
          type yang:counter64;
          config false;
          description
            "The number of Partial List LRPDUs transmitted by the Applicant
            state machine.";
          reference
            "IEEE 802.1CS Clause (11.5.10)";
        }
        leaf accepted-partials {
          type yang:counter64;
          config false;
          description
            "The number of valid Partial List LRPDUs received by the Applicant
            state machine."; 
          reference
            "IEEE 802.1CS Clause (11.5.11)";
        }
        leaf discarded-partials {
          type yang:counter64;
          config false;
          description
            "The number of invalid Partial List LRPDUs discarded by the
            Applicant state machine."; 
          reference
            "IEEE 802.1CS Clause (11.5.12)";
        }
        leaf sent-complete  {
          type yang:counter64;
          config false;
          description
            "The number of Complete List LRPDUs transmitted by the Applicant
            state machine."; 
          reference
            "IEEE 802.1CS Clause (11.5.13)";
        }
        leaf accepted-completes {
          type yang:counter64;
          config false;
          description
            "The number of valid Complete List LRPDUs received by the Applicant
            state machine."; 
          reference
            "IEEE 802.1CS Clause (11.5.14)";
        }
        leaf discarded-completes{
          type yang:counter64;
          config false;
          description
            "The number of invalid Complete List LRPDUs discarded by the
            Applicant state machine."; 
          reference
            "IEEE 802.1CS Clause (11.5.15)";
        }
        leaf discarded-unknowns {
          type yang:counter64;
          config false;
          description
            "The number of LRPDUs of unknown type discarded by the Applicant
            state machine or Partial list state machine."; 
          reference
            "IEEE 802.1CS Clause (11.5.16)";
        }
      } // end portal 
      list lrp-dt-instance {
      key "instance-id";
      config false;
      leaf instance-id {
        type uint32;
        config false;
        description
          "Local data transport instance";
        reference
          "IEEE 802.1CS Clause 7";
        }
        leaf active-tcp-open {
          type boolean;
          config false;
          description
            "A Boolean value that is TRUE if and only if instMyAddress and
            instNeighborAddress are TCP addresses and this LRP-DT instance is
            using the active , not the passive , form of TCP OPEN"; 
          reference
            "IEEE 802.1CS Clause (7.3.2.1)";
        }
        leaf my-dt-address {
          type lrp-dt-address-union;
          config false;
          description
            "The address of the local system for this LRP-DT instance; the
            address used as a destination address by the neighbor LRP-DT
            instance. The address includes a type (MAC, IPv4, or IPv6) and an
            address of that type."; 
          reference
            "IEEE 802.1CS Clause (7.3.2.2)";
        }
        leaf my-tcp-port{
          type inet:port-number;
          config false;
          description
            "The local port number for this TCP connection, or 0, if this
            connection uses ECP, instead of TCP."; 
          reference
            "IEEE 802.1CS Clause (7.3.2.3)";
        }
        leaf neighbor-dt-address {
          type lrp-dt-address-union;
          config false;
          description
            "The address of the neighbor LRP-DT instance; the address used as a
            destination address by this LRP-DT instance. The address includes a
            type (MAC, IPv4, or IPv6) and an address of that type."; 
          reference
            "IEEE 802.1CS Clause (7.3.2.4)";
        }
        leaf neighbor-tcp-port {
          type inet:port-number;
          config false;
          description
            "The remote port number for this TCP connection, or 0, if this
            connection uses ECP, instead of TCP."; 
          reference
            "IEEE 802.1CS Clause (7.3.2.5)";
        }
        leaf discarded-lrpdus {
          type yang:counter64;
          config false;
          description
            "A counter indicating the number of LRPDUs discarded by the LRP-DT
            instance that cannot be assigned to a Portal for processing.";
          reference
            "IEEE 802.1CS Clause (11.4.1)";
        } 
      } // end lrp-dt-instance
    } // end lrp
  } // end augment system
} // end ieee802-dot1cs-lrp
